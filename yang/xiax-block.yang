module xiax-block {
  yang-version 1.1;
  namespace "https://watsen.net/xiax";
  prefix "xb";

  import ietf-inet-types {
    prefix inet;
    reference "RFC 6991: Common YANG Data Types";
  }

  import ietf-restconf {
    prefix rc;
    reference "RFC 8040: RESTCONF Protocol";
  }

  organization "Watsen Networks";

  contact "Kent Watsen <mailto:kent+ietf@watsen.net>";

  description
   "This module defines the data model for xiax data block.

    Copyright (c) 2019 Watsen Networks.  All rights reserved.";


  revision "YYYY-MM-DD" {
    description
     "Initial version";
  }


  rc:yang-data "xiax-block" {

    container xiax-block {

      description
        "Contains lists of inclusions that were processed by `xiax`
         during its 'packing' step.";
  
      list inclusion {
        key path;
  
        description
          "A list of inclusions, one for each <artwork> and/or
           <sourcecode> element processed by `xiax`.";
  
        leaf path {
          type string;
          description
            "The DOM path of the <artwork> or <sourcecode> element.";
        }

        container src {
          leaf attrib {
            type inet:uri;
            description
              "The original 'xiax:src' attribute that was in the 
               <artwork> or <sourcecode> element.";
          }
        }

        container gen {
          leaf attrib {
            type inet:uri;
            description
              "The original 'xiax:gen' attribute that was in the 
               <artwork> or <sourcecode> element.";
          }
          anydata file {
            description
              "The content of the file per the 'xiax:gen' attribute";
          }
        }

        container val {
          leaf attrib {
            type inet:uri;
            description
              "The original 'xiax:val' attribute that was in the 
               <sourcecode> element (<artwork> cannot be validated).";
          }
          anydata file {
            description
              "The content of the file per the 'xiax:val' attribute";
          }
        }

      } // end list inclusion
    } // end container xiax-block
  } // end yang-data
} // end module
